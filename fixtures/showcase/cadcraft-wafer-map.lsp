;; cadcraft-wafer-map.lsp — WAFERMAP: a die map on a round wafer (CadCraft Great Eight showcase; made up to show the tools).
;; A die whose four corners are inside the edge exclusion is whole (outline + solid fill); one crossing the wafer edge is an outline.
(defun wm:ask (msg def / v) (setq v (getreal (strcat "\n" msg " <" (rtos def 2 2) ">: "))) (if v v def))
(defun wm:box (lay x0 y0 x1 y1)
  (entmake (list '(0 . "LWPOLYLINE") '(100 . "AcDbEntity") (cons 8 lay) '(100 . "AcDbPolyline") '(90 . 4) '(70 . 1)
    (list 10 x0 y0) (list 10 x1 y0) (list 10 x1 y1) (list 10 x0 y1))))
(defun wm:fill (lay x0 y0 x1 y1)
  (entmake (list '(0 . "HATCH") '(100 . "AcDbEntity") (cons 8 lay) '(100 . "AcDbHatch") '(2 . "SOLID") '(70 . 1) '(91 . 1) '(92 . 2) '(93 . 4)
    (list 10 x0 y0) (list 10 x1 y0) (list 10 x1 y1) (list 10 x0 y1))))
(defun wm:text (lay x y h s)
  (entmake (list '(0 . "TEXT") (cons 8 lay) (list 10 x y) (cons 40 h) (cons 1 s))))
(defun wm:fl (i n) (if (< i 0) (- (/ (+ i 1) n) 1) (/ i n)))
(defun wm:in (x y r) (<= (+ (* x x) (* y y)) (* r r)))
(defun c:WAFERMAP (/ d w h g ex fx fy fw fh r re nx ny i j x0 y0 x1 y1 a b c e whole edge est)
  (setq d (wm:ask "Wafer diameter" 300.0) w (wm:ask "Die width" 6.0) h (wm:ask "Die height" 4.5)
        g (wm:ask "Scribe lane" 0.1) ex (wm:ask "Edge exclusion" 3.0)
        fx (fix (wm:ask "Exposure field, dies across" 4)) fy (fix (wm:ask "Exposure field, dies down" 7))
        r (/ d 2.0) re (- r ex) whole 0 edge 0
        nx (fix (+ 1 (/ r (+ w g)))) ny (fix (+ 1 (/ r (+ h g)))))
  (setq j (- ny))
  (while (< j ny)
    (setq i (- nx))
    (while (< i nx)
      (setq x0 (+ (* i (+ w g)) (/ g 2.0)) y0 (+ (* j (+ h g)) (/ g 2.0)) x1 (+ x0 w) y1 (+ y0 h))
      (setq a (wm:in x0 y0 re) b (wm:in x1 y0 re) c (wm:in x1 y1 re) e (wm:in x0 y1 re))
      (cond
        ((and a b c e) (wm:fill (if (= 0 (rem (+ (wm:fl i fx) (wm:fl j fy) 1000) 2)) "WAFER-DIE-FILL" "WAFER-DIE-FILL-B") x0 y0 x1 y1) (wm:box "WAFER-DIE" x0 y0 x1 y1) (setq whole (1+ whole)))
        ((or (wm:in x0 y0 r) (wm:in x1 y0 r) (wm:in x1 y1 r) (wm:in x0 y1 r)) (wm:box "WAFER-DIE-EDGE" x0 y0 x1 y1) (setq edge (1+ edge))))
      (setq i (1+ i)))
    (setq j (1+ j)))
  ;; exposure fields: fx x fy dies per shot, drawn where a field reaches the wafer
  (setq fw (* fx (+ w g)) fh (* fy (+ h g)) j (- (fix (+ 1 (/ r fh)))))
  (while (< (* j fh) r)
    (setq i (- (fix (+ 1 (/ r fw)))))
    (while (< (* i fw) r)
      (setq x0 (* i fw) y0 (* j fh) x1 (+ x0 fw) y1 (+ y0 fh))
      (if (or (wm:in x0 y0 r) (wm:in x1 y0 r) (wm:in x1 y1 r) (wm:in x0 y1 r)) (wm:box "WAFER-FIELD" x0 y0 x1 y1))
      (setq i (1+ i)))
    (setq j (1+ j)))
  (entmake (list '(0 . "CIRCLE") '(8 . "WAFER") (list 10 0.0 0.0) (cons 40 r)))
  (entmake (list '(0 . "CIRCLE") '(8 . "WAFER-EXCLUSION") (list 10 0.0 0.0) (cons 40 re)))
  (entmake (list '(0 . "LWPOLYLINE") '(100 . "AcDbEntity") '(8 . "WAFER") '(100 . "AcDbPolyline") '(90 . 3) '(70 . 0)
    (list 10 -1.5 (- r)) (list 10 0.0 (+ (- r) 1.0)) (list 10 1.5 (- r))))
  (setq est (fix (- (/ (* pi r r) (* w h)) (/ (* pi d) (sqrt (* 2.0 w h))))))
  (wm:text "WAFER-TEXT" (+ r 45) 128 9.0 (strcat (rtos d 2 0) " mm wafer"))
  (wm:text "WAFER-TEXT" (+ r 45) 112 5.0 (strcat "Die " (rtos w 2 1) " x " (rtos h 2 1) " mm, scribe " (rtos g 2 2) " mm"))
  (wm:text "WAFER-TEXT" (+ r 45) 104 5.0 (strcat "Edge exclusion " (rtos ex 2 1) " mm"))
  (wm:text "WAFER-TEXT" (+ r 45) 96 5.0 (strcat "Exposure field " (itoa fx) " x " (itoa fy) " dies"))
  (wm:text "WAFER-TEXT" (+ r 45) 79 7.0 (strcat (itoa whole) " whole dies"))
  (wm:text "WAFER-TEXT" (+ r 45) 70 5.0 (strcat (itoa edge) " partial dies at the edge"))
  (wm:text "WAFER-TEXT" (+ r 45) 55 5.0 (strcat "Textbook estimate: " (itoa est)))
  (wm:text "WAFER-TEXT" (+ r 45) 47 4.0 "pi(d/2)^2/S - pi d/sqrt(2S), no scribe, no exclusion")
  (princ (strcat "\nWAFERMAP: " (itoa whole) " whole, " (itoa edge) " partial, estimate " (itoa est)))
  (princ))
